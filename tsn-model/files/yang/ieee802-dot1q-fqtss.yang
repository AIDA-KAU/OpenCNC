module ieee802-dot1q-fqtss {

  namespace "urn:ietf:params:xml:ns:yang:smiv2:ieee802-dot1q-fqtss";
  prefix "fqtss";

  import SNMPv2-TC {
    prefix "snmpv2-tc";
  }

  import ietf-yang-smiv2 {
    prefix "smiv2";
  }

  organization
   "IEEE 802.1 Working Group";

  contact
   "  WG-URL: http://grouper.ieee.org/groups/802/1/index.html
    WG-EMail: stds-802-1@ieee.org
    
     Contact: IEEE 802.1 Working Group Chair
      Postal: C/O IEEE 802.1 Working Group
              IEEE Standards Association
              445 Hoes Lane
              P.O. Box 1331
              Piscataway
              NJ 08855-1331
              USA
      E-mail: STDS-802-1-L@LISTSERV.IEEE.ORG";

  description
   "The Bridge MIB module for managing devices that support
    the Forwarding and Queuing Enhancements
    for Time Sensitive Streams.
    
    Unless otherwise indicated, the references in this MIB
    module are to IEEE Std 802.1Q-2014.
    
    Copyright (C) IEEE (2014).
    This version of this MIB module is part of IEEE802.1Q;
    see the draft itself for full legal notices.";

  revision 2014-12-15 {
    description
     "Published as part of IEEE Std 802.1Q 2014 revision.
      Cross references updated and corrected.";
  }

  revision 2011-02-27 {
    description
     "Minor edits to contact information etc. as part of 
      2011 revision of IEEE Std 802.1Q.";
  }

  revision 2009-10-01 {
    description
     "Initial revision, included in IEEE 802.1Qav.";
  }

  typedef IEEE8021FqtssTrafficClassValue {
    type uint32 {
      range "0..7";
    }
    description
     "An 802.1 FQTSS traffic class value.
      This is the numerical value associated with a traffic
      class in a Bridge. Larger values are associated with
      higher priority traffic classes.";
    reference
     "12.20.1";
    smiv2:display-hint "d";
  }

  typedef IEEE8021FqtssDeltaBandwidthValue {
    type uint32 {
      range "0..100000000";
    }
    description
     "An 802.1 FQTSS delta bandwidth percentage,
      represented as a fixed point number scaled by
      1,000,000.";
    reference
     "12.20.1, 34.4";
    smiv2:display-hint "d";
  }

  typedef IEEE8021FqtssTxSelectionAlgorithmIDValue {
    type uint32;
    description
     "An 802.1 transmission selection algorithm identifier
      value. This is an integer, with the following
      interpretation placed on the value:
      
      0: Strict priority algorithm,
      1: Credit-based shaper algorithm,
      2-255: Reserved for future standardization,
      256-4294967295: Vendor-specific transmission selection
                      algorithm identifiers, consisting of a 
                      four-octet integer, where the most
                      significant 3 octets hold an OUI or CID value,
                      and the least significant octet holds
                      an integer value in the range 0-255
                      assigned by the owner of the OUI or CID.";
    reference
     "8.6.8, 12.20.2";
    smiv2:display-hint "d";
  }

  container ieee802-dot1q-fqtss {
    container ieee8021FqtssBapTable {
      description
       "A table containing a set of bandwidth availability 
        parameters for each traffic class that supports the 
        credit-based shaper algorithm.
        All writable objects in this table must be
        persistent over power up restart/reboot.";
      reference
       "12.20.1";
      smiv2:oid "0.16.1.1.1";

      list ieee8021FqtssBapEntry {
        key "ieee8021BridgeBaseComponentId ieee8021BridgeBasePort ieee8021FqtssBAPTrafficClass";
        description
         "A list of objects containing bandwidth allocation
          information for each traffic class that supports the
          credit-based shaper algorithm. Rows in the table are
          automatically created and deleted as a result of the 
          operation of the algorithm described in 34.5. ";
        smiv2:oid "0.16.1.1.1.1";
        
        leaf ieee8021BridgeBaseComponentId {
          type uint32 {
            range "1..4294967295";
          }
          description
           "The component identifier is used to distinguish between the 
            multiple virtual bridge instances within a PBB.  In simple 
            situations where there is only a single component the default 
            value is 1.";
        }
        
        leaf ieee8021BridgeBasePort {
          type string;
          description
            "The name of the port for which this entry 
             contains bridge management information.";
        }
        
        leaf ieee8021FqtssBAPTrafficClass {
          type fqtss:IEEE8021FqtssTrafficClassValue;
          description
           "The traffic class number associated with the row of
            the table.
            
            A row in this table is created for each traffic class
            that supports the credit-based shaper algrithm. The
            recommended mappings of priorities to traffic classes
            for support of the credit-based shaper algorithm are
            described in 34.5.";
          reference
           "12.20.2, 34.3, 34.5";
          smiv2:max-access "not-accessible";
          smiv2:oid "0.16.1.1.1.1.1";
        }

        leaf ieee8021FqtssDeltaBandwidth {
          type fqtss:IEEE8021FqtssDeltaBandwidthValue;
          units "percent";
          description
           "The value of the deltaBandwidth parameter
            for the traffic class.
            This value is represented as a fixed point number
            scaled by a factor of 1,000,000; i.e., 100,000,000
            (the maximum value) represents 100%.
            
            The default value of the deltaBandwidth parameter 
            for the highest numbered traffic class that supports
            the credit-based shaper algorithm is 75%; for all
            lower numbered traffic classes that support the
            credit-based shaper algorithm the default value is 0%.
            
            The value of this object MUST be retained across
            reinitializations of the management system.";
          reference
           "12.20.1, 34.3";
          smiv2:max-access "read-write";
          smiv2:oid "0.16.1.1.1.1.2";
        }

        leaf ieee8021FqtssOperIdleSlopeMs {
		  config false;
          type uint32;
          units "bits per second";
          description
           "The most significant 32 bits of the bandwidth, 
            in bits per second, that is currently allocated to the
            traffic class (idleSlope(N)). This object MUST be read  
            at the same time as ieee8021FqtssOperIdleSlopeLs, 
            which represents the LS 32 bits of the value, in order
            for the read operation to succeed.
            
            If SRP is supported and in operation, then the reserved  
            bandwidth is determined by the operation of SRP; otherwise, 
            the value of ieee8021FqtssOperIdleSlopeMs is equal to 
            the value of ieee8021FqtssAdminIdleSlopeMs.
            
            The value of this object MUST be retained across
            reinitializations of the management system.";
          reference
           "12.20.1, 34.3";
          smiv2:max-access "read-only";
          smiv2:oid "0.16.1.1.1.1.3";
        }

        leaf ieee8021FqtssOperIdleSlopeLs {
		  config false;
          type uint32;
          units "bits per second";
          description
           "The least significant 32 bits of the bandwidth, 
            in bits per second, that is currently allocated to the
            traffic class (idleSlope(N)). This object MUST be read  
            at the same time as ieee8021FqtssOperIdleSlopeMs, 
            which represents the LS 32 bits of the value, in order
            for the read operation to succeed.
            
            If SRP is supported and in operation, then the reserved  
            bandwidth is determined by the operation of SRP; otherwise, 
            the value of ieee8021FqtssOperIdleSlopeLs is equal to
            the value of ieee8021FqtssAdminIdleSlopeMs.
            
            The value of this object MUST be retained across
            reinitializations of the management system.";
          reference
           "12.20.1, 34.3";
          smiv2:max-access "read-only";
          smiv2:oid "0.16.1.1.1.1.4";
        }
		
        leaf ieee8021FqtssAdminIdleSlopeMs {
          type uint32;
          units "bits per second";
          description
           "The most significant 32 bits of the bandwidth, 
            in bits per second, that the manager desires to allocate
            to the traffic class as  idleSlope(N). This object MUST be  
            read or written at the same time as 
            ieee8021FqtssAdminIdleSlopeLs, 
            which represents the LS 32 bits of the value, in order
            for the read or write operation to succeed.
            
            If SRP is supported and in operation, then the reserved  
            bandwidth is determined by the operation of SRP, and any
            changes to the value of this object have no effect on the
            operational value of idleSlope(N).
            
            The value of this object MUST be retained across
            reinitializations of the management system.";
          reference
           "12.20.1, 34.3";
          smiv2:defval "0";
          smiv2:max-access "read-write";
          smiv2:oid "0.16.1.1.1.1.5";
        }

        leaf ieee8021FqtssAdminIdleSlopeLs {
          type uint32;
          units "bits per second";
          description
           "The least significant 32 bits of the bandwidth, 
            in bits per second, that the manager desires to allocate
            to the traffic class as  idleSlope(N). This object MUST be  
            read or written at the same time as 
            ieee8021FqtssAdminIdleSlopeMs, 
            which represents the LS 32 bits of the value, in order
            for the read or write operation to succeed.
            
            If SRP is supported and in operation, then the reserved  
            bandwidth is determined by the operation of SRP, and any
            changes to the value of this object have no effect on the
            operational value of idleSlope(N).
            
            The value of this object MUST be retained across
            reinitializations of the management system.";
          reference
           "12.20.1, 34.3";
          smiv2:defval "0";
          smiv2:max-access "read-write";
          smiv2:oid "0.16.1.1.1.1.6";
        }

        leaf ieee8021FqtssBapRowStatus {
          type snmpv2-tc:RowStatus;
          description
           "Indicates the status of an entry (row) in this table, and is
            used to create/delete entries.
            
            The corresponding instances of the following objects
            must be set before this object can be made active(1):
               ieee8021FqtssBAPTrafficClass
               ieee8021FqtssDeltaBandwidth
               ieee8021FqtssOperIdleSlopeMs
               ieee8021FqtssOperIdleSlopeLs
               ieee8021FqtssAdminIdleSlopeMs
               ieee8021FqtssAdminIdleSlopeLs
            
            The corresponding instances of the following objects
            may not be changed while this object is active(1):
               ieee8021FqtssBAPTrafficClass";
          smiv2:max-access "read-write";
          smiv2:oid "0.16.1.1.1.1.7";
        }
      }
    }

    container ieee8021FqtssTxSelectionAlgorithmTable {
      description
       "A table containing the assignment of transmission
        selection algorithms to traffic classes for the Port.
        This table provides management of the Transmission
        Selection Algorithm Table defined in 8.6.8.
        
        For a given Port, a row in the table exists for each 
        traffic class that is supported by the Port.
        
        The default assignments of transmission selection 
        algorithms to traffic classes in the table are made
        on instantiation of the table, in accordance
        with the defaults defined in 8.6.8 and 34.5.
        
        All writable objects in this table must be
        persistent over power up restart/reboot.";
      reference
       "8.6.8, 12.20.2, 34.5";
      smiv2:oid "0.16.1.2.1";

      list ieee8021FqtssTxSelectionAlgorithmEntry {
        key "ieee8021BridgeBaseComponentId ieee8021BridgeBasePort ieee8021FqtssTrafficClass";
        description
         "A list of objects that contain the mapping of a
          traffic class value to a transmission selection algorithm
          value.";
        smiv2:oid "0.16.1.2.1.1";
        
        leaf ieee8021BridgeBaseComponentId {
          type uint32 {
            range "1..4294967295";
          }
          description
           "The component identifier is used to distinguish between the 
            multiple virtual bridge instances within a PBB.  In simple 
            situations where there is only a single component the default 
            value is 1.";
        }
        
        leaf ieee8021BridgeBasePort {
          type string;
          description
            "The name of the port for which this entry 
             contains bridge management information.";
        }
        
        leaf ieee8021FqtssTrafficClass {
          type fqtss:IEEE8021FqtssTrafficClassValue;
          description
           "The traffic class to which the transmission selection
            algorithm is assigned.
            
            The value of this object MUST be retained across
            reinitializations of the management system.";
          reference
           "8.6.8, 12.20.2, 34.5";
          smiv2:max-access "not-accessible";
          smiv2:oid "0.16.1.2.1.1.1";
        }

        leaf ieee8021FqtssTxSelectionAlgorithmID {
          type fqtss:IEEE8021FqtssTxSelectionAlgorithmIDValue;
          description
           "The identifier of the transmission selection algorithm
            assigned to the traffic class.
            
            The value of this object MUST be retained across
            reinitializations of the management system.";
          reference
           "8.6.8, 12.20.2, 34.5";
          smiv2:max-access "read-write";
          smiv2:oid "0.16.1.2.1.1.2";
        }
      }
    }

    container ieee8021FqtssSrpRegenOverrideTable {
      description
       "A table containing the set of priority regeneration 
        table override values for the Port.
        
        The recommended default values of priorities
        associated with SR classes, and the corresponding 
        override values, are defined in 6.9.4. 
        
        All writable objects in this table must be
        persistent over power up restart/reboot.";
      reference
       "35.1.4, 6.9.4, 12.20.3";
      smiv2:oid "0.16.1.2.2";

      list ieee8021FqtssSrpRegenOverrideEntry {
        key "ieee8021BridgeBaseComponentId ieee8021BridgeBasePort ieee8021FqtssSrClassPriority";
        description
         "A list of objects that contain the mapping of a
          priority value to a priority regeneration override
          value, and a boundary port indication.
          Rows in the table exist for all priorities that are
          associated with SR classes.";
        smiv2:oid "0.16.1.2.2.1";
        
        leaf ieee8021BridgeBaseComponentId {
          type uint32 {
            range "1..4294967295";
          }
          description
           "The component identifier is used to distinguish between the 
            multiple virtual bridge instances within a PBB.  In simple 
            situations where there is only a single component the default 
            value is 1.";
        }
        
        leaf ieee8021BridgeBasePort {
          type string;
          description
            "The name of the port for which this entry 
             contains bridge management information.";
        }
        
        leaf ieee8021FqtssSrClassPriority {
          type uint32 {
              range "0..7";
          }
          description
           "The priority value that is overridden at the
            SRP domain boundary. ";
          reference
           "35.1.4, 6.9.4, 12.20.3";
          smiv2:max-access "not-accessible";
          smiv2:oid "0.16.1.2.2.1.1";
        }

        leaf ieee8021FqtssPriorityRegenOverride {
          type uint32 {
              range "0..7";
          }
          description
           "The priority value that is used to override the
            priority regeneration table entry at the SRP
            domain boundary.
            
            The value of this object MUST be retained across
            reinitializations of the management system.";
          reference
           "35.1.4, 6.9.4, 12.20.3";
          smiv2:max-access "read-write";
          smiv2:oid "0.16.1.2.2.1.2";
        }
		leaf ieee8021FqtssSrpBoundaryPort {
		  config false;
          type boolean;
          description
           "The value of the SRPdomainBoundaryPort parameter
            (35.1.4) for the priority. ";
          reference
           "35.1.4, 6.9.4, 12.20.3";
          smiv2:max-access "read-only";
          smiv2:oid "0.16.1.2.2.1.3";
        }
      }
    }
  }

  smiv2:alias "ieee8021FqtssMib" {
    smiv2:oid "0.16";
  }

  smiv2:alias "ieee8021FqtssNotifications" {
    smiv2:oid "0.16.0";
  }

  smiv2:alias "ieee8021FqtssObjects" {
    smiv2:oid "0.16.1";
  }

  smiv2:alias "ieee8021FqtssBap" {
    smiv2:oid "0.16.1.1";
  }

  smiv2:alias "ieee8021FqtssMappings" {
    smiv2:oid "0.16.1.2";
  }

  smiv2:alias "ieee8021FqtssConformance" {
    smiv2:oid "0.16.2";
  }

  smiv2:alias "ieee8021FqtssCompliances" {
    smiv2:oid "0.16.2.1";
  }

  smiv2:alias "ieee8021FqtssGroups" {
    smiv2:oid "0.16.2.2";
  }

}
